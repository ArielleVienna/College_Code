FME workspace Well Permit Notification.fmw

Parameters:
- SourceDataset_XLSXR = C:\Users\wood22975\Downloads\Wells.xlsx   # Source Microsoft Excel File(s)
- DestDataset_XLSXW = C:\Users\wood22975\Downloads\Intersection.xlsx   # Destination Microsoft Excel File
- DestDataset_XLSXW_3 = C:\Users\wood22975\Documents\FME\Workspaces\Intersect Wells.xlsx   # Destination Microsoft Excel File
- SourceDataset_XLSXR_3 = C:\Users\wood22975\Documents\FME\Workspaces\Intersect Wells.xlsx   # Source Microsoft Excel File(s)

Readers:
- XLSXR_1: XLSXR from $(SourceDataset_XLSXR) in NAD83.Texas/EqArea
- XLSXR_2: XLSXR from $(SourceDataset_XLSXR_3)

Writers:
- XLSXW_1: XLSXW to $(DestDataset_XLSXW)
- XLSXW_2: XLSXW to $(DestDataset_XLSXW_3)

Test Wells (reader XLSXR_1)
    attributes: ID number(3,0), API number(11,0), Permit Date date, Lat (NAD83) number(9,6), Abstract char(6), Terminus Point char(30), Penetration Point char(30), PP Lat number(7,4), PP Long number(8,4), TP Long number(8,4), Long (NAD83) x_coordinate, TP Lat  y_coordinate
    -> Bufferer
Bufferer
    ANGLE = 22.5
    CAP_STYLE = Round
    CORNER_STYLE = Round
    GROUP_BY = "PP Lat" "TP Lat " "PP Long" "TP Long"
    MODE = AREA
    OFFSET = 0.5
    BUFFERED -> Bufferer_2
Bufferer_2
    ANGLE = 22.5
    CAP_STYLE = Round
    CORNER_STYLE = Round
    MODE = AREA
    OFFSET = 1
    BUFFERED -> Intersector
    BUFFERED -> Test Wells (writer XLSXW_2)
Intersector
    ATTRS_ACCUM_MODE = Use Attributes From One Feature
    CLEANING_TOLERANCE = None
    DEAGGREGATE_INPUT = Yes
    DUPLICATE_Z_NODES = No
    GENERATE_LIST_DROP = NO
    MEASURE_TYPE = Continuous
    NODE_NUM_ATTR = _node_number
    OV_ATTR = _overlaps
    PERFORM_SELF_INTERSECTION = No
    SEG_ATTR = _segments
    SEPARATE_COLLINEAR_SEGMENTS = No
    INTERSECTED -> intersected (writer XLSXW_1)
intersected (writer XLSXW_1)
    attributes: ID number(3), API number(11), Permit Date date(20), Lat (NAD83) number(9), Abstract string(6), Terminus Point string(30), Penetration Point string(30), PP Lat number(7), PP Long number(8), TP Long number(8), Long (NAD83) number(20), TP Lat  number(20)
Test Wells (writer XLSXW_2)
    attributes: ID number(3), API number(11), Permit Date date(20), Lat (NAD83) number(9), Abstract string(6), Terminus Point string(30), Penetration Point string(30), PP Lat number(7), PP Long number(8), TP Long number(8), Long (NAD83) number(20), TP Lat  number(20)
Test Wells (reader XLSXR_2)
    attributes: ID number(3,0), API number(11,0), Permit Date date, Lat (NAD83) number(9,6), Abstract char(6), Terminus Point char(30), Penetration Point char(30), PP Lat number(7,4), TP Long number(8,4), Long (NAD83) number(10,6), PP Long x_coordinate, TP Lat  y_coordinate
    -> Emailer
Emailer
    ATTACHGROUP = No
    BODY = You have a well within a 1/2 mile or a mile distance of a newly approved permit. Check the Texas Railroad Commission for more information.
    FROM = Veebean@gmail.com
    SERVICE = Gmail
    SMTP_CONNECTION = GMAIL_NAMED_CONNECTION;veebean@gmail.com;TIMEOUT;60;FME_CONTROLLER_QUERY_FILE;transformers\dependencies\emailer\Gmail.fme
    SUBJECT = Well Permit Approved Near You
    TO = Wood22975@tamu.edu
